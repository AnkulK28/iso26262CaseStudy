# SSRS
Software Safety Requirement Specification for the Highway Lane Following Controller.

## SW_HLF#6: HLF Path Planning (Container)
The HLF component shall predict future waypoint based on current lane information.

### SW_HLF#6.1: Preview Curvature (Functional)
The CurvaturePrediction shall predict future lane curvature ahead of the ego vehicle for PredictionHorizon based on measured longitudinal velocity and estimated centerline Curvature and Curvature Derivative according to following equation:
previewdCurvature = Curvature+CuvatureDerivative*longitudinalVelocity*t
where t = 0:Ts:Ts*PredictionHorizon

### SW_HLF#6.2: Preview Curvature Horizon (Functional)
The curvature preview shall produce predictions for up to 3 seconds.

## SW_HLF#5: HLF Input Conditioning (Container)
Inputs to the HLF system shall be conditioned to be forwarded to the MPC controller.

### SW_HLF#5.3: Leading Car Detection (Container)
The HLF shall identify the leading vehicle among other traffic participants producing

#### SW_HLF#5.3.1: Identification of leading car (Functional)
The HLF system shall identify the leading vehicle among other traffic participants within the same lane boundaries based on the relative distance to ego vehicle.

#### SW_HLF#5.3.2: Information about Leading Car (Functional)
The HLF system shall compute the distance and velocity of the leading vehicle relative to the ego vehicle.

### SW_HLF#5.2: LaneCenter Conditioning for Coordinate systems (Functional)
The HLF component shall convert the centerline parametrization coefficient from the ISO 8855 (x in direction of travel and y to the left) to SAE J670E coordinate systems (x in the direction of travel and y to the right of the vehicle).
Note: This basically means to apply a unary minus to all lane coefficients.

### SW_HLF#5.1: Lane Center Estimation (Container)
The HLF software shall estimate the lane centerline from the detected lane boundaries and their parametrizations,

#### SW_HLF#5.1.2: Estimate lane center (Container)
Depending on the detection strength of each lane side, one of the following estimation methods shall be selected:

##### SW_HLF#5.1.2.1: Estimate Lane Center from Left and Right Boundaries (Software Functional)
When detection strength of left and right lanes are above accepted threshold, the EstimateLaneCenter shall interpolate the centerline from parametrized curves for both sides.

##### SW_HLF#5.1.2.2: Estimate Lane Center from Left Boundaries (Software Functional)
When only the detection strength of left lane boundary is above accepted threshold, the EstimateLaneCenter shall estimate the centerline from parametrized curves for left side only.

##### SW_HLF#5.1.2.3: Estimate Lane Center from Right Boundaries only (Software Functional)
When only the detection strength of right lane boundary is above accepted threshold, the EstimateLaneCenter shall estimate the centerline from parametrized curves for left side only.

##### SW_HLF#5.1.2.4: Estimate Lane Center without reliable lane boundary detections (Software Functional)
In absence of reliable information about lane boundaries, the lane center at any point shall be assumed to be equivalent to the previous estimate.

#### SW_HLF#5.1.1: Lane Centerline (Software Functional)
The lane centerline shall be parametrized as a third order polynomial (a*x^3+b*x^2+c*x+d) where:
a denotes CurvatureDerivative of the centerline
b denotes Curvature of the centerline
c denotes HeadingAngle of the centerline
d denotes LateralOffset of the centerline

## SW_HLF#1: Intended Functionality of the HLF (Informational)
The HLF system shall provide sufficient steering and acceleration/deceleration to the vehicle steering and braking systems, respectively, to keep the vehicle centered in the highway lane based on the following information:
* Estimated lane boundaries detected by the lane detection component
* Estimated position of other traffic participants (vehicles)
* Velocity set by the ACC system
* Measured vehicle velocity
Assumptions:
- The Lane Detection component shall detect the left and right boundaries of the current lane, assigning a strength metric of such detections.
- The Detection of other traffic participants shall detect and track all vehicles in the surroundings of the ego vehicle.

## SW_HLF#4: HLF Assumptions for Inputs (Container)
The HLF controller shall receive information about the lane boundaries and other vehicles in the surrounding in the following format:

### SW_HLF#4.2: Detected Traffic Participants (Software Interface)
The traffic participants detection component shall detect other traffic participants detailing for each participant its
State: [x,vx,y,yx,z,vz] where [x,y,z] is the 3D position of each participant velocity [Vx,Vy,Vz]
TrackID: for identification and tracking
The traffic participants detection component shall assume ISO 8855 compliant coordinate system (i.e., x in the direction of travel, y to the left of the vehicle and z points upwards from the ground).

### SW_HLF#4.1: Lanes Information (Software Interface)
The Lane Detection component shall pack information about the detected lanes detailing for each side:
- CurvatureDerivative:
- Curvature
- HeadingAngle
- LateralOffset
- Strength
- XExtent
- BoundaryType
The first four attributes are the parametrization coefficients for each lane side as a third order polynomial (ax^3+bx^2+cx+d).
Strength refers to the strength of the detection.
XExtent and BoundaryType may not be used by the HLF system.
The lane detection shall assume ISO 8855 compliant coordinate system (i.e., x in the direction of travel, y to the left of the vehicle and z points upwards from the ground).

## SW_HLF#7: HLF Controllers (Container)
The HLF Controller shall determine the steering and acceleration commands to be sent to the vehicle foundational systems.

### SW_HLF#7.3: Controller Mode Selection (Functional)
The Controller Mode Selection shall decide upon the acceleration to be forwarded to vehicle foundational components based on the status of watchdog controller, its required deceleration and required acceleration computed by the MPC controller.

### SW_HLF#7.1: Path following Controller (Container)

#### SW_HLF#7.1.1: Leading Vehicle Limiters (Functional)
When the leading car is found to be further than 1000m, the relative velocity of the leading car input to the MPC controller shall be set to 0 and the relative distance is set to 200m.

#### SW_HLF#7.1.4: MPC Path Following Controller (Functional)
The HLF component shall use the Path Following Controller from the MPC toolbox to provide steering and acceleration commands based on:
- SetVelocity
- LongitudinalVelocity
- Curvature
- LateralDeviation
- RelativeYawAngle
- RelativeDistanc
- RelativeVelocity
- TimeGap

##### SW_HLF#7.1.4.1: Default spacing (Functional)
The path following controller shall maintain a safe distance between the ego vehicle and lead vehicle. This distance shall be default_spacing.

##### SW_HLF#7.1.4.2: Vehicle Model (Functional)
The path following controller shall consider the vehicle parameters as defined in the system level

##### SW_HLF#7.1.4.3: Operational Limits (Software Functional)
The HLF shall have the following operational limits:
Minimum steering angle (rad): min_steer
Maximum steering angle (rad): max_steer
Minimum longitudinal acceleration (m/s^2): min_ac
Maximum longitudinal acceleration (m/s^2): max_ac

##### SW_HLF#7.1.4.4: Vehicle dynamics model (Functional)
The MPC Controller shall consider a vehicle dynamics model consistent with the car model specified in system requirements.

#### SW_HLF#7.1.3: Time Gap (Functional)
Time Gap shall be set to 1.5 seconds.

#### SW_HLF#7.1.2: Longitudinal Velocity Limiters (Functional)
Longitudinal Velocity shall be limited to the range [0.00001, 100] m/s.

### SW_HLF#7.2: Watchdog Controller (Container)
The watchdog controller shall only intervene in transient conditions to avoid a collision by monitoring the relative distance and relative velocity of the leading vehicle.

#### SW_HLF#7.2.1: Time to Collision Calculation (Software Functional)
The watchdog controller shall compute Time to collision (time needed to collide with the leading vehicle) as
(distanceToLeadingVehicle-headwayOffset)/|relativeVelocityOfLeadingVehicle|, where |.| denotes the absolute value.

#### SW_HLF#7.2.3: Stopping Time Calculations (Software Functional)
The watchdog controller shall compute at each step four critical times based on the measure longitudinal velocity
FCWStoppingTime = timeToReact + egoVelocity/driver_decel
PB1StoppingTime = timeMargin + egoVelocity/PB1_decel
PB2StoppingTime = timeMargin + egoVelocity/PB2_decel
FBStoppingTime = timeMargin + egoVelocity/FB_decel
respectively, computing at each time step the required time to stop the vehicle if
- the driver is warned considering time to react
- an automatic deceleration is applied with PB1_decel
- an automatic deceleration is applied with PB2_decel
- an automatic deceleration is applied with full brake (FB_decel).

#### SW_HLF#7.2.4: Watchdog Braking Logic (Container)
The watchdog controller shall issue one of the following deceleration commands (0, PB1_decel, PB2_decel, FB_decel) depending on time to collision and computed Stopping times.

##### SW_HLF#7.2.4.1: Driver warning (Functional)
The watchdog controller shall request no deceleration if the user is able to avoid a collision when warned assuming a time to react.

##### SW_HLF#7.2.4.2: Partial Braking Level 1 (Functional)
The Watchdog controller shall apply PB1_decel if
- computed time to collision goes less that time needs to stop the car if applying PB1_decel
- leading vehicle is slower than ego vehicle

##### SW_HLF#7.2.4.3: Partial Braking Level 2 (Functional)
The Watchdog controller shall apply PB2_decel if
- computed time to collision goes less that time needs to stop the car if applying PB2_decel
- leading vehicle is slower than ego vehicle

##### SW_HLF#7.2.4.4: Full Braking (Functional)
The Watchdog controller shall apply Full braking if
- computed time to collision goes less that time needs to stop the car if applying full brake
- leading vehicle is slower than ego vehicle
or when distance to leading vehicle drops below default spacing

##### SW_HLF#7.2.4.5: Idle state (Functional)
The Watchdog controller shall apply no braking if the vehicle has stopped or current velocity does not lead to a collision.

##### SW_HLF#7.2.4.6: Stopped Vehicle (Functional)
The Watchdog controller shall consider a velocity < 0.1 as a stopped vehicle.

#### SW_HLF#7.2.2: Time to Collision guard against division by zero (Software Property)
The calculation of the time to collision shall put limits on the relative velocity of the leading car to guard against division by zero and implausible values. These values shall be [0.01, 100].

## SW_HLF#2: HLF timing (Container)
The HLF controller shall run in realtime.

### SW_HLF#2.1: HLF update time (Software Property)
The HLF controller shall update its outputs each 0.1 s.
- Rationale: Control cycle of 0.1 s is sufficient to allow the vehicle to react to rapid changes in the environment.
