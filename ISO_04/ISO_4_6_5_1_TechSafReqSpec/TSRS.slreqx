# TSRS
These highway lane following control requirements are partially adapted from ISO 15622

## SYS_HLF#1: HLF Modes of Operation (Functional)
The HLF system shall have the following three modes of operation:
1) Off
2) Standby
3) Activel

### SYS_HLF#2: Off Mode (Functional)
In the Off mode the HLF system shall not control the vehicle speed and will ignore speed set commands.

#### SYS_HLF#2.1: Power Up Condition (Functional)
The HLF system shall enter the Off mode at power up of the system.

#### SYS_HLF#2.2: Disengage Condition (Functional)
The HLF system shall enter the Off mode when the driver has manually disengaged the system.

### SYS_HLF#3: Standby Mode (Functional)
In the Standby mode the HLF system shall not control the vehicle speed but will recognize speed set commands.

#### SYS_HLF#3.1: Engage Condition (Functional)
The HLF system shall enter the Standby mode when the driver manually engages the system.

#### SYS_HLF#3.2: Disengage Condition (Functional)
The HLF system shall leave the Standby mode and revert to the Off mode, when the driver manually disengages the system.

#### SYS_HLF#3.3: Speed Set Condition (Functional)
The HLF system shall leave the Standby mode and enter the Active mode, when the driver manually sets the speed target and it is above the operational minimum value and the brake is not active.

### SYS_HLF#4: Active Mode (Functional)
In the Active mode the HLF system shall control the vehicle speed (Speed Control) or the time gap between this vehicle and any forward vehicle in the same lane (Following Control).

#### SYS_HLF#4.1: Speed Control Mode (Functional)
In the Speed Control sub-mode the HLF system shall control the vehicle speed based on the driver selected speed target.

##### SYS_HLF#4.1.1: Standby to Speed Control Condition (Functional)
The HLF system shall enter the Speed Control mode from the Standby mode, when the driver manually sets the speed target and it is above the operational minimum value and the brake is not active.

##### SYS_HLF#4.1.2: Speed Control to Standby Condition (Functional)
The HLF system shall transition from Speed Control mode to Standby mode when the driver activates the brakes.

##### SYS_HLF#4.1.3: Speed Control to Off Condition (Functional)
The HLF system shall transition from Speed Control mode to Off mode when the driver disengages the system.

##### SYS_HLF#4.1.4: Speed Control to Following Control Condition (Functional)
The HLF system shall transition from Speed Control mode to Following Control mode when the time gap between this vehicle and any forward vehicle in the same lane is less than or equal to the minimum allowed time gap.

#### SYS_HLF#4.2: Following Control Mode (Functional)
In the Following Control sub-mode the adaptive cruise control system shall control the minimum time gap between this vehicle and any forward vehicle in the same lane.

##### SYS_HLF#4.2.1: Following Control to Standby Condition (Functional)
The HLF system shall transition from Following Control mode to Standby mode when the driver activates the brakes.

##### SYS_HLF#4.2.2: Following Control to Off Condition (Functional)
The HLF system shall transition from Following Control mode to Off mode when the driver disengages the system.

##### SYS_HLF#4.2.3: Following Control to Speed Control Condition (Functional)
The HLF system shall transition from Following Control mode to Speed Control mode when the time gap between this vehicle and any forward vehicle in the same lane is greater than the minimum allowed time gap for at least TBD seconds.

## SYS_HLF#5: HLF Driver Interface (Functional)
The driver interface shall provide the following:
1) Engage button
2) Disengage button
3) Speed Increment/Resume button
4) Speed Decrement/Set button
5) Brake pedal active switch
6) HLF status display

### SYS_HLF#5.2: Target Speed Selection (Functional)
Target speed selection and adjustment shall be controlled via buttons mounted on the steering wheel.
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
#### SYS_HLF#5.2.1: Set Button Usage (Functional)
When the HLF is in the Standby Mode and the driver pushes the -Set Button, the HLF shall enter the Active Mode and set the target speed to the current vehicle speed.

#### SYS_HLF#5.2.2: Increment Button Usage (Functional)
When the HLF is in the Active Mode and the driver pushes the +Res Button, the HLF system shall increase the target speed by 1 kmh.

#### SYS_HLF#5.2.3: Decrement Button Usage (Functional)
When the HLF is in the Active Mode and the driver pushes the -Set Button, the HLF system shall decrease the target speed by 1 kmh.

#### SYS_HLF#5.2.4: Resume Button Usage (Functional)
When the HLF is in the Standby Mode with a target speed already set and the driver pushes the +Res Button, the HLF shall enter the Active Mode and leave the target speed at the current value.

#### SYS_HLF#5.2.5: Brake Pedal Usage (Functional)
When the HLF is in the Active Mode and the driver pushes the brake pedal, the HLF shall latch the target speed at its current value and enter the Standby Mode.

### SYS_HLF#5.3: Driver Displays (Functional)
The HLF system shall display the system status and target speed on the driver display near the speedometer.

#### SYS_HLF#5.3.1: Off Mode Status (Functional)
When the cruise control is in the Off Mode, the driver status and speed targets shall be hidden with nothing displayed.

#### SYS_HLF#5.3.2: Standby Mode Status (Functional)
When the HLF is in the Standby Mode, the driver status shall be displayed via a white HLF symbol.
HLF symbol can be the same as Cruise control symbol:
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
#### SYS_HLF#5.3.3: Active Mode - Speed Control Status (Functional)
When the HLF is in the Standby Mode, the driver status shall be displayed via a green HLF symbol.
HLF symbol can be the same as Cruise control symbol:
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
#### SYS_HLF#5.3.4: Active Mode - Following Control Status (Functional)
When the HLF is in the Standby Mode, the driver status shall be displayed via an amber HLF symbol.
HLF symbol can be the same as Cruise control symbol:
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
#### SYS_HLF#5.3.5: Target Speed Display - Not Set (Functional)
When the HLF is in the Standby Mode and the target speed has not yet been set, the speed target shall be displayed as two white dashes (--).

#### SYS_HLF#5.3.7: Target Speed Display - Speed Control Mode (Functional)
When the HLF is in the Speed Control Mode, the speed target shall be displayed as two green numerals.

#### SYS_HLF#5.3.8: Target Speed Display - Following Control Mode (Functional)
When the HLF is in the Following Control Mode, the speed target shall be displayed as two amber numerals.

#### SYS_HLF#5.3.6: Target Speed Display - Standby Mode (Functional)
When the HLF is in the Standby Mode and the speed has been set, the speed target shall be displayed as two white numerals.

## SYS_HLF#6: HLF Performance Requirements (Container)
The following sections detail the performance requirements for speed control mode and following control mode.

### SYS_HLF#6.2: Speed Control Performance (Container)
The following sections contain the speed control mode performance requirements for the HLF system.

#### SYS_HLF#6.2.2: Capture Performance with Shallow Grade (Functional)
When the grade of the road is less than 4%, the vehicle shall capture a change in the target speed with no more than 2 kmh overshoot.

#### SYS_HLF#6.2.3: Tracking Performance with Steep Grade (Informational)
When the grade of the road is greater than or equal to 4%, the vehicle tracking may be adversely affected by pedal position limits, engine torque capabilities, transmission and tire friction.

#### SYS_HLF#6.2.4: Capture Performance with Steep Grade (Functional)
When the grade of the road is greater than or equal to 4%, the vehicle capture of a change in target speed may be adversely affected by pedal position limits, engine torque capabilities, transmission gear and tire friction.

#### SYS_HLF#6.2.1: Tracking Performance with Shallow Grade (Functional)
When the grade of the road is less than 4%, the vehicle shall track the target speed within 1 kmh steady state.

### SYS_HLF#6.3: Following Control Performance (Container)
The following sections contain the following control mode performance requirements for the HLF system.

#### SYS_HLF#6.3.1: Minimum Time Gap (Functional)
The minimum time gap to the next forward vehicle shall be 2 seconds.

#### SYS_HLF#6.3.2: Minimum Clearance (Functional)
The minimum clearance to the next forward vehicle shall be current speed * 2 seconds.

#### SYS_HLF#6.3.3: Transient Conditions and Collision Avoidance (Technical Safety Requirement)
Under a transient condition where the clearance falls below the minimum, the HLF shall reduce the speed in order to attain the minimum clearance.

### SYS_HLF#6.1: Operational Limits (Container)
The following sections contain the operational limits for the HLF system.

#### SYS_HLF#6.1.1: Minimum Target Speed (Functional)
The minimum target speed that can be selected by the driver shall be 24 kmh (or 6.66 m/s).

#### SYS_HLF#6.1.2: Minimum Operating Speed (Functional)
The minimum operating speed with the HLF in active mode shall be 16 kmh (4.44 m/s).

#### SYS_HLF#6.1.3: Maximum Target Speed (Functional)
The maximum target speed that can be selected by the driver shall be 160 kmh (or 45 m/s).

#### SYS_HLF#6.1.4: Maximum Acceleration (Functional)
The maximum acceleration while in active mode shall be 2 m/s^2

#### SYS_HLF#6.1.5: Maximum Deceleration (Functional)
The maximum deceleration while in active mode shall be 3m/s^2.

#### SYS_HLF#6.1.6: Maximum Rate of Change of Deceleration (Functional)
The maximum rate of change in deceleration while in active mode shall be 0.23 m/sec^3.

#### SYS_HLF#6.1.7: Curve radius capability (Functional)
The system shall robustly drive in curves having radius greater than 125 m.

### SYS_HLF#6.4: Lateral Control Performance (Functional)
In both, speed control and following control modes, the HLF shall steer the vehicle to be centered in the current lane.

#### SYS_HLF#6.4.2: Minimum steering angle (Functional)
The Lane Keeping feature shall have a minimum Steering angle of 0.01 rad

#### SYS_HLF#6.4.1: Maximum steering Angle (Functional)
The Lane Keeping feature shall have a maximum steering angle of 0.26 rad.

## SYS_CarModel#1: Car Model Specs (Functional)
The following lists the car model specs:
| Parameter | Description | value | Unit |
| --- | --- | --- | --- |
| m | Total mass of vehicle | 1575 | kg |
| I_z | Yaw moment of inertia of vehicle | 2875 | m*N*s^2 |
| Cf | Cornering stiffness of front tires | 19000 | N/rad |
| Cr | Cornering stiffness of rear tires | 33000 | N/rad |
| lf | Longitudinal distance from c.g. to front tires | 1.5130 | m |
| lr | Longitudinal distance from c.g. to rear tires | 1.3050 | m |
| tau | Longitudinal acceleration tracking time constant | 0.5 | s |
more details on this model can be found in https://www.mathworks.com/help/vdynblks/ref/sedan.html
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
## SYS_HLF#7: HLF Detection Capabilities (Container)
The HLF system shall detect other traffic participants and the lane boundaries of the subject vehicle.

### SYS_HLF#7.1: Detection of lead car (Functional)
The HLF system shall detect the leading vehicle.

### SYS_HLF#7.2: Leading Vehicle Discrimination (Functional)
If there is more than one forward vehicle on straight roads or in curved roads, the forward vehicle in the ego vehicle's lane shall be selected to follow.

### SYS_HLF#7.4: Lane Boundary detection (Functional)
The HLF system shall detect the boundaries of the lane in which the vehicle is present.

### SYS_HLF#7.3: Attributes of the leading vehicle (Functional)
The HLF shall compute the lead car relative_distance and relative_velocity.

## SYS_IntendedFunction: Intended Function (Informational)
The highway lane following functionality allows the vehicle to remain within the lane boundaries and maintain a speed set by the driver. The vehicle enters following mode when the presence of a leading car does not permit the speed set by the driver, and in this case, the vehicle shall maintain a time gap to the leading vehicle.

## SYS_Definitions#1: Terms and Definitions (Informational)
For the purpose of this document, the following terms and definitions apply.

### SYS_Definitions#1.1: Time gap and clearance (Functional)
Time gap shall be computed as v/c (s), where v is the longitudinal velocity (m/s) of the vehicle and c denote clearance (m).
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Clearance is defined as the distance between the front surface of the ego vehicle and the rear surface of the leading vehicle.

### SYS_Definitions#1.2: Lead Car or forward Vehicle (Functional)
vehicle in front of and moving in the same direction and travelling on the same roadway as the subject vehicle

### SYS_Definitions#1.3: Set speed (Functional)
desired travel speed, as set by the driver or by another system external to the HLF system.

### SYS_Definitions#1.4: Target Vehicle (Functional)
Vehicle that the subject vehicle follows
